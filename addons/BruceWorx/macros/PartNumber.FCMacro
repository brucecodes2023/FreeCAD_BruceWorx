# SPDX-License-Identifier: LGPL-2.1-or-later
# BruceWorx part-number macro (FCB-P2-04/05).
#
# Sets each chosen object's Label, and the document Label, to the next
# {PROG}-{DT}-{PPPPP}-{SSS}-{REV} number (example: LE-01-01001-001-A).
#
# Program: BW_PROGRAM, or the only program in the numbering file.
# Document type: BW_DOCUMENT_TYPE or BW_DT (01, 02, ...). See
#   config/document_types.json — the shipped codes are placeholders.
# Parent: BW_PARENT (PPPPP) to take the next sub-assembly under that drawing.
#   Omit it to reserve a new parent and start at sub 001.
# Config: BW_NUMBERING_CONFIG, or config/numbering.json (created from the
#   example on first allocate).
# Objects: the GUI selection, or solid roots (a Body, not its Pad).
#   Extra objects in one run share the parent and take 002, 003, ...
#
# FreeCAD cannot rename a document's internal Name after creation. The
# visible document name follows the saved file stem. Hyphens in that stem
# become underscores in the internal Name (LE_01_01001_001_A).
#
# Headless equivalent:
#   FreeCADCmd -- addons/BruceWorx/hooks.py rename \
#     --input part.FCStd --program LE --document-type 01

import os
import sys

_addon = os.path.dirname(os.path.dirname(os.path.abspath(__file__)))
if _addon not in sys.path:
    sys.path.insert(0, _addon)

from bruceworx.macro import run  # noqa: E402

_result = run(
    program=os.environ.get("BW_PROGRAM") or None,
    document_type=os.environ.get("BW_DOCUMENT_TYPE") or os.environ.get("BW_DT") or None,
    config=os.environ.get("BW_NUMBERING_CONFIG") or None,
    revision=os.environ.get("BW_REVISION") or None,
    parent=os.environ.get("BW_PARENT") or None,
)
print("BW_RESULT " + __import__("json").dumps(_result, sort_keys=True))
