# SPDX-License-Identifier: LGPL-2.1-or-later
# Snapshot preferences before BruceWorx.cfg is merged. Failures are logged
# and swallowed: a raised exception aborts the pack and nothing is applied.
import os
import sys


def _warn(message):
    try:
        import FreeCAD

        FreeCAD.Console.PrintWarning(message + "\n")
    except Exception:
        print(message)


def _ensure_mod_path():
    try:
        import FreeCAD as App
    except Exception:
        return
    home = App.getHomePath()
    for candidate in (
        os.path.join(home, "Mod", "BruceWorx"),
        os.path.join(home, "share", "Mod", "BruceWorx"),
    ):
        if os.path.isdir(candidate) and candidate not in sys.path:
            sys.path.insert(0, candidate)


try:
    _ensure_mod_path()
    import bruceworx_pack

    bruceworx_pack.freecad_pre("light")
except Exception as exc:
    _warn(f"BruceWorx pre.FCMacro: {exc}")
